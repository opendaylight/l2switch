module stp-status-aware-node-connector {
  yang-version 1;
  namespace "urn:opendaylight:l2switch:loopremover";
  prefix loopremover;

  import odl-codegen-extensions {
    prefix oce;
  }
  import opendaylight-inventory {
    prefix inv;
    revision-date 2013-08-19;
  }

  description
    "Loop remover stp status aware Data Model";

  revision 2014-07-14 {
    description
      "l2switch loop remover module draft.";
  }

  typedef stp-status {
    type enumeration {
      enum "forwarding" {
        value 1;
        description "STP Status Forwarding";
      }
      enum "discarding" {
        value 2;
        description "STP status discarding";
      }
    }
  }

  grouping stp-status-node-connector {
    leaf status {
      type stp-status;
    }
  }
  augment "/inv:nodes/inv:node/inv:node-connector" {
    oce:augment-identifier "stp-status-aware-node-connector";
    uses stp-status-node-connector;
  }
}
