module host-tracker-impl {

  yang-version 1;
  namespace "urn:opendaylight:l2switch:host-tracker-impl";
  prefix "host-tracker-impl";

  import config { prefix config; revision-date 2013-04-05; }
  import opendaylight-md-sal-binding { prefix mdsal; revision-date 2013-10-28; }

  description
    "This module contains the base YANG definitions for
    host-tracker-impl implementation.";

  revision 2014-05-28 {
    description "Initial module draft.";
  }

  // This is the definition of the service implementation as a module identity.
  identity host-tracker-impl {
    base config:module-type;

    // Specifies the prefix for generated java classes.
    config:java-name-prefix HostTracker;
  }

  // Augments the 'configuration' choice node under modules/module.
  // We consume the three main services, RPCs, DataStore, and Notifications
  augment "/config:modules/config:module/config:configuration" {
    case host-tracker-impl {
      when "/config:modules/config:module/config:type = 'host-tracker-impl'";

      leaf topology-id {
        type string;
      }
      leaf host-purge-interval {
        type int64;
        mandatory true;
        description "The interval at which to evaluate whether hosts should be removed in seconds";
      }
      leaf host-purge-age{
        type int64;
        mandatory true;
        description "How long a host must have been unobserved for it to be removed in seconds";
      }
      container notification-service {
        uses config:service-ref {
          refine type {
            mandatory true;
            config:required-identity mdsal:binding-notification-service;
          }
        }
      }
      container data-broker {
        uses config:service-ref {
          refine type {
            mandatory false;
            config:required-identity mdsal:binding-async-data-broker;
          }
        }
      }
    }
  }
}
