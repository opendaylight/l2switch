module ethernet-decoder-config {
  yang-version 1;
  namespace "urn:opendaylight:ethernetdecoder:config";
  prefix edconfig;

  import config { prefix config; revision-date 2013-04-05; }
  import packet-decoder-config { prefix pdcoonf; revision-date 2014-05-28; }

  description "Service definition for ethernet decoder implemetation";

  revision "2014-05-28" {
    description "Initial revision";
  }

  // Service definition for packet decoder service
  identity ethernet-decoder-impl {
      description "ethernet decoder implementation definition";
      base "config:module-type";
      config:java-name-prefix "EthernetDecoder";
  }

  // Configuration for module
  augment "/config:modules/config:module/config:configuration" {
    case ethernet-decoder-impl {
      when "/config:modules/config:module/config:type = 'ethernet-decoder-impl'";
      // Dependency on bar service instance
      container packet-decoder-service {
       uses config:service-ref {
         refine type {
           mandatory true;
           config:required-identity pdcoonf:packet-decoder-service;
         }
       }
      }
    }
  }

  // Runtime state definition for module
  augment "/config:modules/config:module/config:state" {
     case ethernet-decoder-impl {
         when "/config:modules/config:module/config:type = 'ethernet-decoder-impl'";
     }
  }
}
