module packet-decoder-config {
  yang-version 1;
  namespace "urn:opendaylight:packetdecoder:config";
  prefix pconfig;

  import config { prefix config; revision-date 2013-04-05; }

    description
        "Service definition for packet decoder service";

    revision "2014-05-28" {
        description
            "Initial revision";
    }

    // Service definition for packet decoder service
    identity packet-decoder-service {
        description
            "packet decoder service definition";

        base "config:service-type";
        config:java-class "org.opendaylight.l2switch.packethandler.decoders.PacketDecoderService";
    }
}
