module packet-decoder-impl-config {
 
    yang-version 1;
    namespace "urn:opendaylight:packetdecoder:config:impl";
    prefix "pconfig-impl";
 
    // Dependency on service definition for config-demo
    /* Service definitions could be also located in this yang file or even
     * in a separate maven project that is marked as maven dependency
     */
    import packet-decoder-config { prefix pconfig; revision-date 2014-05-28;}
 
    // Dependencies on config subsystem definition
    import config { prefix config; revision-date 2013-04-05; }
    import rpc-context { prefix rpcx; revision-date 2013-06-17; }
    import opendaylight-md-sal-binding { prefix mdsal; revision-date 2013-10-28; }
 
 
    description
        "Service implementation for packet decoder";
 
    revision "2014-05-28" {
        description
            "Initial revision";
    }
    // identity for implementing module
    identity packet-decoder-impl {
        base config:module-type;                                           
        config:provided-service pconfig:packet-decoder-service;
        config:java-name-prefix PacketDecoderImpl;
    }                                                                      
                                                                           
    // Configuration for module
    augment "/config:modules/config:module/config:configuration" {         
        case packet-decoder-impl {
            when "/config:modules/config:module/config:type = 'packet-decoder-impl'";
                                                                           

            // Dependency on bar service instance                          
            container notification-service {
                uses config:service-ref {
                    refine type {
                        mandatory true;
                        config:required-identity mdsal:binding-notification-service;
                    }
                }
            }
        }
    }                                                                      
                                                                           
    // Runtime state definition for module
    augment "/config:modules/config:module/config:state" {                 
        case packet-decoder-impl {
            when "/config:modules/config:module/config:type = 'packet-decoder-impl'";
        }
    }
}
