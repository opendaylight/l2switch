module arp-handler-impl {

  yang-version 1;
  namespace "urn:opendaylight:packet:arp-handler-impl";
  prefix "arp-handler-impl";

  import config { prefix config; revision-date 2013-04-05; }
  import opendaylight-md-sal-binding { prefix mdsal; revision-date 2013-10-28; }

  description
    "This module contains the base YANG definitions for
    arphandler-impl implementation.";

  revision 2014-05-28 {
    description "Initial module draft.";
  }

  // This is the definition of the service implementation as a module identity.
  identity arp-handler-impl {
    base config:module-type;

    // Specifies the prefix for generated java classes.
    config:java-name-prefix ArpHandler;
  }

  // Augments the 'configuration' choice node under modules/module.
  augment "/config:modules/config:module/config:configuration" {
    case arp-handler-impl {
      when "/config:modules/config:module/config:type = 'arp-handler-impl'";

      container notification-service {
        uses config:service-ref {
          refine type {
            mandatory true;
            config:required-identity mdsal:binding-notification-service;
          }
        }
      }
      container data-broker {
        uses config:service-ref {
          refine type {
            mandatory false;
            config:required-identity mdsal:binding-async-data-broker;
          }
        }
      }
      container rpc-registry {
        uses config:service-ref {
          refine type {
            mandatory true;
            config:required-identity mdsal:binding-rpc-registry;
          }
        }
      }
    }
  }
}
